ProtocolModule
    { iso org(3) dod(6) internet(1) private(4)
      enterprise(1) mojomir(1024) software(1)
      bbTT(16) proto(2) wut(1) 1 }
DEFINITIONS AUTOMATIC TAGS ::=
BEGIN

Command ::= CHOICE {
	bbhwnd BBHwndMsg,
	bbcmd BBCmd
}

BBHwndMsg ::= SEQUENCE {
	hwnd    INTEGER
}

BBCmd ::= SEQUENCE {
	cmd    OCTET STRING
}

END
